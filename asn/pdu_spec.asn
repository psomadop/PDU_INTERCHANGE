TestModule DEFINITIONS ::= BEGIN


AComplexType ::= SEQUENCE {
    clockTicks     INTEGER(0..65536),          --- Let's say we have a 16bit clock ticks counter.
    intSequence    SEQUENCE OF INTEGER         --- A sequence of integers.
}

Cell ::= CHOICE {
    intVal	        INTEGER  (0..4),           -- A 4-bit integer value.
    boolVal	        BOOLEAN,
    name            OCTET STRING,
    message         AComplexType
}

PDU ::= SEQUENCE {
    cells   SEQUENCE OF Cell    --- This is a cell array. Whatever each cell is.
}

END
